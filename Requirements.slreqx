# Requirements

## #1: System: Motor should have 1900 <= x <= 2100 rpm after 40 seconds for at least 5 seconds (Functional)

## #2: Component: PI controller outputs should be 0 <= x <= 1 all the time (Functional)
